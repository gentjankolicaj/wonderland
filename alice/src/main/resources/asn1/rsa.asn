RSA DEFINITIONS ::=
BEGIN


-- imports from other modules
IMPORTS Algorithm FROM ALGORITHM;


-- Public key definition , this outputs the public key in PKCS1v2 format
RSAPublicKeyASN1 ::= SEQUENCE{
 modulus INTEGER, --n
 publicExponent INTEGER --e
}


-- Private key definition , this outputs the key in PKCS1v2 format.
RSAPrivateKeyASN1 ::= SEQUENCE {
 version Version OPTIONAL,
 modulus INTEGER, -- n
 publicExponent INTEGER, -- e
 privateExponent INTEGER, -- d
 primeP INTEGER, -- p
 primeQ INTEGER, -- q
 primeExponentP INTEGER OPTIONAL, -- d mod (p-1)
 primeExponentQ INTEGER OPTIONAL, -- d mod (q-1)
 coefficient INTEGER, -- (inverse of q) mod p
 otherPrimeInfos OtherPrimeInfos OPTIONAL
}


-- Version definition with asn1
Version ::= INTEGER


-- OtherPrimeInfos definition
OtherPrimeInfos ::= SEQUENCE {
 parameters ANY DEFINED BY RSA OPTIONAL
}


-- Cipher definition
RSAASN1 ::= SEQUENCE {
 algorithm Algorithm,
 publicKey RSAPublicKeyASN1,
 privateKey RSAPrivateKeyASN1
}

END
